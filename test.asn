EUTRA-RRC-Definitions DEFINITIONS AUTOMATIC TAGS ::= 
BEGIN 
{
  ItemId ::= SEQUENCE 
    { 
     partnumber IA5String, 
     quantity INTEGER, 
     wholesaleprice REAL,  
     saleprice REAL  
    }  
}
END
